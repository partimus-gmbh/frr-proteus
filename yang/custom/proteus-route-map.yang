module proteus-route-map {
  yang-version 1.1;
  namespace "https://github.com/robinchrist/frr-proteus/yang/custom/route-map";
  prefix proteus-route-map;

  import ietf-inet-types {
    prefix inet;
  }
  import ietf-yang-types {
    prefix yang;
  }
  import proteus-types {
    prefix pt;
  }
  import proteus-filter {
    prefix filter;
  }
  import proteus-bgp-filter {
    prefix bgpfilter;
  }
  import proteus-interface {
    prefix intf;
  }

  organization
    "frr-proteus";
  contact
    "https://github.com/robinchrist/frr-proteus";
  description
    "FRR route-map configuration: the generic route-map machinery from
     lib/routemap_cli.c ('route-map NAME <permit|deny> SEQ', description,
     call, on-match, plus the daemon-independent match/set clauses) and
     the full BGP match/set vocabulary registered by bgpd/bgp_routemap.c.
     Match/set clauses from other daemons (ospfd, zebra 'set src', ...)
     are NOT modeled -- frr-proteus is BGP-only.

     Every leaf's description cites the CLI line it renders to; the
     grammar was taken from the DEFPY/DEFUN command strings in the two
     files above. FRR stores most match/set arguments as opaque strings
     and re-emits them verbatim on config write, so leaves whose values
     FRR never parses beyond tokenization (community strings, AS path
     strings, ...) are plain strings here too.

     Referential integrity: other modules point at route-maps via
     leafref to /route-map/name, and 'call' below does the
     same. References *from* route-maps to filtering objects are
     leafrefs into the proteus modules that model them:
     prefix-lists/access-lists (proteus-filter), as-path access-lists
     and community/extcommunity/large-community lists plus community
     aliases (proteus-bgp-filter), interfaces (proteus-interface).
     Legacy numbered community-list references ((1-99)/(100-500)) are
     not expressible -- numbered lists are excluded from
     proteus-bgp-filter (named lists only). References to objects
     still not modeled (VRFs) stay plain strings with a
     'TODO(leafref)' comment.";

  revision 2026-07-05 {
    description
      "Initial revision.";
  }

  list route-map {
    key "name";
    description
      "One route-map: an ordered sequence of entries
       (lib/routemap_cli.c route_map_instance_cmd:
       'route-map RMAP_NAME <deny|permit> (1-65535)').";

    leaf name {
      type string {
        length "1..max";
      }
      description
        "Route-map name (RMAP_NAME).";
    }

    list entry {
      key "sequence";
      description
        "One 'route-map NAME <permit|deny> SEQ' block. All match
         clauses of an entry must match for the action to apply
         (logical AND); an entry with no match clauses matches
         everything.";

      leaf sequence {
        type uint16 {
          range "1..65535";
        }
        description
          "Entry ordering number.";
      }

      leaf action {
        type enumeration {
          enum permit {
            description
              "Matching routes are accepted and the set clauses
               applied.";
          }
          enum deny {
            description
              "Matching routes are rejected.";
          }
        }
        mandatory true;
        description
          "The <deny|permit> token of the entry header.";
      }

      leaf description {
        type string;
        description
          "'description LINE...' (route_map_description_cmd).";
      }

      leaf call {
        type leafref {
          path "/route-map/name";
        }
        description
          "'call WORD': jump to another route-map; if it denies the
           route, processing stops (route_map_call_cmd).";
      }

      leaf on-match {
        type union {
          type enumeration {
            enum next {
              description
                "'on-match next': continue with the next entry after
                 a match.";
            }
          }
          type uint16 {
            range "1..65535";
          }
        }
        description
          "Exit policy on match: 'on-match next' or
           'on-match goto (1-65535)' (a sequence number; FRR's
           'continue N' is an alias for the goto form)
           (route_map_onmatch_next_cmd / route_map_onmatch_goto_cmd).";
      }

      container match {
        description
          "Match clauses. At most one clause of each type per entry
           (configuring a second one of the same type replaces the
           first -- FRR CLI semantics). NOTE: several clause pairs
           are mutually exclusive in FRR (e.g. 'match ip address'
           via access-list vs. prefix-list replace each other);
           that exclusivity is not expressed here -- YANG 'choice'
           would work but the CLI treats them as one slot, which a
           renderer must respect anyway.";

        leaf interface {
          type leafref {
            path "/intf:interface/intf:name";
          }
          description
            "'match interface IFNAME' (lib/routemap_cli.c).";
        }

        leaf ip-address {
          type leafref {
            path "/filter:access-lists/filter:ipv4/"
               + "filter:access-list/filter:name";
          }
          description
            "'match ip address ACCESSLIST4_NAME'
             (lib/routemap_cli.c).";
        }
        leaf ip-address-prefix-list {
          type leafref {
            path "/filter:prefix-lists/filter:ipv4/"
               + "filter:prefix-list/filter:name";
          }
          description
            "'match ip address prefix-list PREFIXLIST4_NAME'
             (lib/routemap_cli.c).";
        }
        leaf ip-next-hop {
          type leafref {
            path "/filter:access-lists/filter:ipv4/"
               + "filter:access-list/filter:name";
          }
          description
            "'match ip next-hop ACCESSLIST4_NAME'
             (lib/routemap_cli.c).";
        }
        leaf ip-next-hop-prefix-list {
          type leafref {
            path "/filter:prefix-lists/filter:ipv4/"
               + "filter:prefix-list/filter:name";
          }
          description
            "'match ip next-hop prefix-list PREFIXLIST4_NAME'
             (lib/routemap_cli.c).";
        }
        leaf ip-next-hop-address {
          type inet:ipv4-address-no-zone;
          description
            "'match ip next-hop address A.B.C.D'
             (bgp_routemap.c match_ip_next_hop_address_cmd).";
        }
        leaf ip-next-hop-type-blackhole {
          type boolean;
          description
            "'match ip next-hop type blackhole'
             (lib/routemap_cli.c).";
        }
        leaf ip-route-source {
          type leafref {
            path "/filter:access-lists/filter:ipv4/"
               + "filter:access-list/filter:name";
          }
          description
            "'match ip route-source ACCESSLIST4_NAME'
             (bgp_routemap.c).";
        }
        leaf ip-route-source-prefix-list {
          type leafref {
            path "/filter:prefix-lists/filter:ipv4/"
               + "filter:prefix-list/filter:name";
          }
          description
            "'match ip route-source prefix-list PREFIXLIST_NAME'
             (bgp_routemap.c).";
        }

        leaf ipv6-address {
          type leafref {
            path "/filter:access-lists/filter:ipv6/"
               + "filter:access-list/filter:name";
          }
          description
            "'match ipv6 address ACCESSLIST6_NAME'
             (lib/routemap_cli.c).";
        }
        leaf ipv6-address-prefix-list {
          type leafref {
            path "/filter:prefix-lists/filter:ipv6/"
               + "filter:prefix-list/filter:name";
          }
          description
            "'match ipv6 address prefix-list PREFIXLIST6_NAME'
             (lib/routemap_cli.c).";
        }
        leaf ipv6-next-hop {
          type leafref {
            path "/filter:access-lists/filter:ipv6/"
               + "filter:access-list/filter:name";
          }
          description
            "'match ipv6 next-hop ACCESSLIST6_NAME'
             (lib/routemap_cli.c).";
        }
        leaf ipv6-next-hop-prefix-list {
          type leafref {
            path "/filter:prefix-lists/filter:ipv6/"
               + "filter:prefix-list/filter:name";
          }
          description
            "'match ipv6 next-hop prefix-list PREFIXLIST_NAME'
             (lib/routemap_cli.c).";
        }
        leaf ipv6-next-hop-address {
          type inet:ipv6-address-no-zone;
          description
            "'match ipv6 next-hop address X:X::X:X'
             (bgp_routemap.c).";
        }
        leaf ipv6-next-hop-type-blackhole {
          type boolean;
          description
            "'match ipv6 next-hop type blackhole'
             (lib/routemap_cli.c).";
        }

        leaf metric {
          type uint32;
          description
            "'match metric (0-4294967295)' (lib/routemap_cli.c).";
        }
        leaf tag {
          type union {
            type enumeration {
              enum untagged;
            }
            type uint32 {
              range "1..4294967295";
            }
          }
          description
            "'match tag <untagged|(1-4294967295)>'
             (lib/routemap_cli.c).";
        }
        leaf local-preference {
          type uint32;
          description
            "'match local-preference (0-4294967295)'
             (bgp_routemap.c).";
        }
        leaf origin {
          type enumeration {
            enum egp;
            enum igp;
            enum incomplete;
          }
          description
            "'match origin <egp|igp|incomplete>' (bgp_routemap.c).";
        }
        leaf probability {
          type uint8 {
            range "0..100";
          }
          description
            "'match probability (0-100)': match this percentage of
             routes (bgp_routemap.c).";
        }
        leaf alias {
          type leafref {
            path "/bgpfilter:community-alias/bgpfilter:name";
          }
          description
            "'match alias ALIAS_NAME': community alias defined with
             'bgp community alias' (bgp_routemap.c).";
        }

        leaf as-path {
          type leafref {
            path "/bgpfilter:as-path-access-list/bgpfilter:name";
          }
          description
            "'match as-path AS_PATH_FILTER_NAME' (bgp_routemap.c).";
        }

        container community {
          description
            "'match community COMMUNITY_LIST_NAME
             [<exact-match|any>]' (bgp_routemap.c). The legacy
             numbered form ((1-99)/(100-500)) is not expressible:
             numbered lists are excluded from proteus-bgp-filter.";
          leaf list-name {
            type leafref {
              path "/bgpfilter:community-list/bgpfilter:name";
            }
            description
              "Community list name.";
          }
          leaf match-style {
            type enumeration {
              enum exact-match {
                description
                  "Communities must match the list exactly.";
              }
              enum any {
                description
                  "Match if any list entry matches.";
              }
            }
            description
              "Optional matching mode; unset means FRR's default
               (any community in the list matches).";
          }
        }

        container extcommunity {
          description
            "'match extcommunity EXTCOMMUNITY_LIST_NAME
             [<exact-match|any>]' (bgp_routemap.c). Numbered lists
             are not expressible (see 'match community').";
          leaf list-name {
            type leafref {
              path "/bgpfilter:extcommunity-list/bgpfilter:name";
            }
          }
          leaf match-style {
            type enumeration {
              enum exact-match;
              enum any;
            }
          }
        }

        container large-community {
          description
            "'match large-community LCOMMUNITY_LIST_NAME
             [<exact-match|any>]' (bgp_routemap.c). Numbered lists
             are not expressible (see 'match community').";
          leaf list-name {
            type leafref {
              path "/bgpfilter:large-community-list/bgpfilter:name";
            }
          }
          leaf match-style {
            type enumeration {
              enum exact-match;
              enum any;
            }
          }
        }

        leaf mac-address {
          type leafref {
            path "/filter:access-lists/filter:mac/"
               + "filter:access-list/filter:name";
          }
          description
            "'match mac address ACCESSLIST_MAC_NAME'
             (bgp_routemap.c).";
        }

        leaf peer {
          type union {
            type inet:ip-address-no-zone;
            type enumeration {
              enum local {
                description
                  "'match peer local': static or redistributed
                   routes.";
              }
            }
            type string;
          }
          description
            "'match peer <A.B.C.D|X:X::X:X|WORD|local>': the peer
             the route was learned from, by address or interface
             name (bgp_routemap.c).";
        }
        leaf src-peer {
          type union {
            type inet:ip-address-no-zone;
            type string;
          }
          description
            "'match src-peer <A.B.C.D|X:X::X:X|WORD>' (route-map for
             outgoing direction matching the source peer)
             (bgp_routemap.c).";
        }

        leaf source-protocol {
          type enumeration {
            enum babel;
            enum bgp;
            enum connected;
            enum eigrp;
            enum isis;
            enum kernel;
            enum ospf;
            enum ospf6;
            enum rip;
            enum ripng;
            enum sharp;
            enum static;
            enum table;
            enum table-direct;
          }
          description
            "'match source-protocol <protocol>': protocol the route
             was learned via (bgp_routemap.c; the token set is FRR's
             generated FRR_REDIST_STR_ZEBRA list).";
        }
        leaf source-vrf {
          type string;
          description
            "'match source-vrf NAME' (bgp_routemap.c).
             // No leafref: VRFs exist as instance keys in
             // proteus-bgp but a route can be leaked from a VRF
             // with no BGP instance, so a plain name is correct.";
        }

        container evpn {
          description
            "EVPN-specific match clauses (bgp_routemap.c).";
          leaf default-route {
            type boolean;
            description
              "'match evpn default-route': default EVPN type-5
               route.";
          }
          container rd {
            presence
              "An RD match is configured (the encoding choice inside
               is mandatory once present; 'presence' keeps it from
               propagating up as a mandatory node).";
            description
              "'match evpn rd ASN:NN_OR_IP-ADDRESS:NN'.
               The raw case exists precisely for matching malformed
               RDs.";
            uses pt:route-distinguisher;
          }
          leaf route-type {
            type enumeration {
              enum ead {
                description
                  "Type-1 Ethernet Auto-Discovery route.";
              }
              enum macip {
                description
                  "Type-2 MAC/IP advertisement route.";
              }
              enum multicast {
                description
                  "Type-3 inclusive multicast Ethernet tag route.";
              }
              enum es {
                description
                  "Type-4 Ethernet Segment route.";
              }
              enum prefix {
                description
                  "Type-5 IP prefix route.";
              }
            }
            description
              "'match evpn route-type
               <ead|1|macip|2|multicast|3|es|4|prefix|5>' -- FRR
               accepts the numeric aliases on input but always
               writes the keyword, so only keywords are modeled.";
          }
          leaf vni {
            type pt:vni;
            description
              "'match evpn vni (1-16777215)'.";
          }
        }
      }

      container set {
        description
          "Set clauses, applied to routes matched by a permit
           entry. At most one clause of each type per entry.";

        leaf ip-next-hop {
          type union {
            type inet:ipv4-address-no-zone;
            type enumeration {
              enum peer-address {
                description
                  "'set ip next-hop peer-address'.";
              }
              enum unchanged {
                description
                  "'set ip next-hop unchanged'.";
              }
            }
          }
          description
            "'set ip next-hop <A.B.C.D|peer-address|unchanged>'
             (lib/routemap_cli.c + bgp_routemap.c).";
        }
        leaf ipv6-next-hop-global {
          type inet:ipv6-address-no-zone;
          description
            "'set ipv6 next-hop global X:X::X:X' (bgp_routemap.c).";
        }
        leaf ipv6-next-hop-local {
          type inet:ipv6-address-no-zone;
          description
            "'set ipv6 next-hop local X:X::X:X'
             (lib/routemap_cli.c).";
        }
        leaf ipv6-next-hop-peer-address {
          type boolean;
          description
            "'set ipv6 next-hop peer-address' (bgp_routemap.c).";
        }
        leaf ipv6-next-hop-prefer-global {
          type boolean;
          description
            "'set ipv6 next-hop prefer-global' (bgp_routemap.c).";
        }
        leaf ipv4-vpn-next-hop {
          type inet:ipv4-address-no-zone;
          description
            "'set ipv4 vpn next-hop A.B.C.D' (bgp_routemap.c).";
        }
        leaf ipv6-vpn-next-hop {
          type inet:ipv6-address-no-zone;
          description
            "'set ipv6 vpn next-hop X:X::X:X' (bgp_routemap.c).";
        }
        leaf l3vpn-next-hop-encapsulation {
          type enumeration {
            enum gre;
            enum gretap;
          }
          description
            "'set l3vpn next-hop encapsulation <gre|gretap>'
             (bgp_routemap.c).";
        }

        container metric {
          presence
            "A set metric is configured (the operand choice inside
             is mandatory once present; 'presence' keeps it from
             propagating up and making every route-map entry
             require one).";
          description
            "'set metric <(-4294967295-4294967295)|rtt|+rtt|-rtt|
             igp|aigp>' (lib/routemap_cli.c; the semantics live in
             route_value_compile in bgpd/bgp_routemap.c: a bare
             operand sets the metric, a '+'/'-' prefix adds to /
             subtracts from the existing one). Structured instead
             of a sign-carrying value: 'operation' is the prefix,
             the operand is either a real uint32 'value' or one of
             the rtt/igp/aigp 'variable's.";
          leaf operation {
            type enumeration {
              enum set {
                description
                  "Bare operand: set the metric.";
              }
              enum add {
                description
                  "'+' prefix: add to the existing metric.";
              }
              enum subtract {
                description
                  "'-' prefix: subtract from the existing metric.";
              }
            }
            description
              "Unset renders like 'set' (a plain operand). Kept
               without a YANG default: the bindings never apply
               defaults, and unset-means-set keeps the common case
               a single assignment.";
          }

          choice operand {
            mandatory true;
            description
              "What to set/adjust the metric with -- exactly one
               (mandatory choice; the enclosing metric container is
               a presence container, so the choice only bites once
               'set metric' is configured at all).";

            case value {
              leaf value {
                type uint32;
                description
                  "Numeric operand (0-4294967295). The CLI's
                   negative range is the subtract operation, not a
                   negative metric -- MED is unsigned.";
              }
            }

            case variable {
              leaf variable {
                type enumeration {
                  enum rtt {
                    description
                      "The peer's round-trip time; the only
                       variable FRR also accepts with add/subtract
                       ('+rtt' / '-rtt').";
                  }
                  enum igp {
                    description
                      "The IGP metric of the next hop.";
                  }
                  enum aigp {
                    description
                      "The AIGP metric.";
                  }
                }
                must ". = 'rtt' or not(../operation) or
                      ../operation = 'set'" {
                  error-message
                    "only the rtt variable can be added or
                     subtracted";
                }
                description
                  "Variable operand instead of a number.";
              }
            }
          }
        }
        leaf min-metric {
          type uint32;
          description
            "'set min-metric (0-4294967295)' (lib/routemap_cli.c).";
        }
        leaf max-metric {
          type uint32;
          description
            "'set max-metric (0-4294967295)' (lib/routemap_cli.c).";
        }
        leaf tag {
          type union {
            type enumeration {
              enum untagged;
            }
            type uint32 {
              range "1..4294967295";
            }
          }
          description
            "'set tag <untagged|(1-4294967295)>'
             (lib/routemap_cli.c).";
        }
        leaf sr-te-color {
          type uint32 {
            range "1..4294967295";
          }
          description
            "'set sr-te color (1-4294967295)' (lib/routemap_cli.c).";
        }
        leaf table {
          type uint32 {
            range "1..4294967295";
          }
          description
            "'set table (1-4294967295)': kernel routing table for
             this route (bgp_routemap.c).";
        }

        leaf as-path-prepend {
          type string;
          description
            "'set as-path prepend ASNUM...': space-separated AS
             numbers, emitted verbatim (bgp_routemap.c).";
        }
        leaf as-path-prepend-last-as {
          type uint8 {
            range "1..10";
          }
          description
            "'set as-path prepend last-as (1-10)' (bgp_routemap.c).";
        }
        leaf as-path-exclude {
          type string;
          description
            "'set as-path exclude ASNUM...' (bgp_routemap.c).";
        }
        leaf as-path-exclude-access-list {
          type leafref {
            path "/bgpfilter:as-path-access-list/bgpfilter:name";
          }
          description
            "'set as-path exclude as-path-access-list
             AS_PATH_FILTER_NAME' (bgp_routemap.c).";
        }
        leaf as-path-replace {
          type string;
          description
            "'set as-path replace <any|ASNUM> [ASNUM]': the full
             argument text, emitted verbatim (bgp_routemap.c).";
        }
        leaf as-path-replace-access-list {
          type leafref {
            path "/bgpfilter:as-path-access-list/bgpfilter:name";
          }
          description
            "'set as-path replace as-path-access-list
             AS_PATH_FILTER_NAME [ASNUM]' (bgp_routemap.c).";
        }

        container aggregator {
          presence
            "A set aggregator is configured ('presence' scopes the
             must below to configured instances: a non-presence
             container exists implicitly and would fail it on every
             route-map entry).";
          must "(plain or asdot/high) and address" {
            error-message
              "'set aggregator as' takes AS number and address
               together";
          }
          description
            "'set aggregator as ASNUM A.B.C.D' (bgp_routemap.c).
             The ASN is the plain/asdot choice from
             pt:as-number-notation; ASN and address must be set
             together -- a single CLI line (the 'must').";
          uses pt:as-number-notation;
          leaf address {
            type inet:ipv4-address-no-zone;
          }
        }

        leaf aigp-metric {
          type union {
            type enumeration {
              enum igp-metric;
            }
            type uint32;
          }
          description
            "'set aigp-metric <igp-metric|(0-4294967295)>'
             (bgp_routemap.c).";
        }
        leaf atomic-aggregate {
          type boolean;
          description
            "'set atomic-aggregate' (bgp_routemap.c).";
        }
        leaf distance {
          type uint8 {
            range "1..255";
          }
          description
            "'set distance (1-255)' (bgp_routemap.c).";
        }
        leaf label-index {
          type uint32 {
            range "0..1048560";
          }
          description
            "'set label-index (0-1048560)' (bgp_routemap.c).";
        }
        leaf local-preference {
          type uint32;
          description
            "'set local-preference (0-4294967295)'
             (bgp_routemap.c).";
        }
        leaf origin {
          type enumeration {
            enum egp;
            enum igp;
            enum incomplete;
          }
          description
            "'set origin <egp|igp|incomplete>' (bgp_routemap.c).";
        }
        leaf originator-id {
          type yang:dotted-quad;
          description
            "'set originator-id A.B.C.D' (bgp_routemap.c). A BGP
             ORIGINATOR_ID is a router ID: a 32-bit identifier in
             dotted notation (RFC 6991 dotted-quad), not an
             address.";
        }
        leaf weight {
          type uint32;
          description
            "'set weight (0-4294967295)' (bgp_routemap.c).";
        }

        container community {
          must "not(none) or not(member or well-known or raw "
             + "or additive)" {
            error-message
              "'set community none' takes no community values";
          }
          description
            "'set community <AA:NN... [additive]|none>'
             (bgp_routemap.c). Structured values plus a raw
             fallback (for deliberately setting values outside the
             standard forms); 'none' strips the attribute and is
             exclusive with everything else (the 'must').
             Unconfigured when empty.";
          uses pt:community-set;
          leaf additive {
            type boolean;
            description
              "Trailing 'additive': add to the existing communities
               instead of replacing them. Only set true.";
          }
          leaf none {
            type boolean;
            description
              "'set community none': strip the attribute. Only set
               true.";
          }
        }
        leaf comm-list-delete {
          type leafref {
            path "/bgpfilter:community-list/bgpfilter:name";
          }
          description
            "'set comm-list COMMUNITY_LIST_NAME delete'
             (bgp_routemap.c). Numbered lists are not expressible
             (excluded from proteus-bgp-filter).";
        }
        container large-community {
          must "not(none) or not(member or raw or additive)" {
            error-message
              "'set large-community none' takes no values";
          }
          description
            "'set large-community <GA:LD1:LD2... [additive]|none>'
             (bgp_routemap.c), same shape as 'set community'.
             Unconfigured when empty.";
          uses pt:large-community-set;
          leaf additive {
            type boolean;
            description
              "Trailing 'additive'. Only set true.";
          }
          leaf none {
            type boolean;
            description
              "'set large-community none': strip the attribute.
               Only set true.";
          }
        }
        leaf large-comm-list-delete {
          type leafref {
            path "/bgpfilter:large-community-list/bgpfilter:name";
          }
          description
            "'set large-comm-list LCOMMUNITY_LIST_NAME delete'
             (bgp_routemap.c). Numbered lists are not expressible
             (excluded from proteus-bgp-filter).";
        }

        container extcommunity-rt {
          description
            "'set extcommunity rt ASN:NN_OR_IP-ADDRESS:NN...':
             space-separated route-target list (bgp_routemap.c).
             Unconfigured when empty.";
          uses pt:route-target-set;
          leaf-list raw {
            type string;
            description
              "Fallback: RT tokens emitted verbatim, for values
               outside the structured encodings.";
          }
        }
        container extcommunity-nt {
          description
            "'set extcommunity nt NODE-ID:0...': Node Target
             extended communities
             (draft-ietf-idr-node-target-ext-comm, type 0x01
             subtype 0x09; bgp_routemap.c set_ecommunity_nt_cmd,
             parsed by ecommunity_str2com). Each value renders as
             '<node-id>:0' -- the trailing :0 is the reserved
             field, required by FRR's tokenizer. Unconfigured when
             empty.";
          leaf-list node-id {
            type yang:dotted-quad;
            description
              "Target BGP Identifier: a router ID (32-bit
               identifier in dotted notation), not an address.";
          }
          leaf-list raw {
            type string;
            description
              "Fallback: tokens emitted verbatim.";
          }
        }
        container extcommunity-soo {
          description
            "'set extcommunity soo ASN:NN_OR_IP-ADDRESS:NN...':
             space-separated site-of-origin list (bgp_routemap.c).
             Route Origins (RFC 4360 subtype 0x03), NOT route
             targets. Unconfigured when empty.";
          uses pt:route-origin-set;
          leaf-list raw {
            type string;
            description
              "Fallback: SoO tokens emitted verbatim.";
          }
        }
        container extcommunity-color {
          description
            "'set extcommunity color [CO:]COLOR...': Color extended
             communities (RFC 9012 section 4.3; CO bits per RFC
             9256 section 8.8.1; bgp_routemap.c
             set_ecommunity_color_cmd, parsed by
             ecommunity_gettoken's color branch). Unconfigured when
             empty.";
          list color {
            key "value";
            description
              "One color, rendered '<co-flags>:<value>' when the
               CO bits are set and bare '<value>' otherwise.";
            leaf value {
              type uint32 {
                range "1..4294967295";
              }
              description
                "4-byte Color Value.";
            }
            leaf co-flags {
              type enumeration {
                enum "00" {
                  description
                    "Specified color only.";
                }
                enum "01" {
                  description
                    "Color, or null endpoint.";
                }
                enum "10" {
                  description
                    "Color, null endpoint, or any endpoint.";
                }
                enum "11" {
                  description
                    "Reserved combination (FRR accepts it; RFC
                     9256 leaves it undefined).";
                }
              }
              description
                "The two CO bits, spelled in binary exactly as
                 FRR's CLI takes them ('CO:COLOR', CO one of
                 00/01/10/11).";
            }
          }
          leaf-list raw {
            type string;
            description
              "Fallback: tokens emitted verbatim.";
          }
        }
        container extcommunity-bandwidth {
          description
            "'set extcommunity bandwidth <(0-4294967295)|cumulative|
             num-multipaths> [non-transitive]' (bgp_routemap.c).";
          leaf value {
            type union {
              type uint32;
              type enumeration {
                enum cumulative;
                enum num-multipaths;
              }
            }
          }
          leaf non-transitive {
            type boolean;
            default "false";
          }
        }
        leaf extcommunity-none {
          type boolean;
          description
            "'set extcommunity none': strip all extended communities
             (bgp_routemap.c).";
        }

        container evpn-gateway-ip {
          description
            "'set evpn gateway-ip <ipv4 A.B.C.D|ipv6 X:X::X:X>':
             overlay index gateway IP for EVPN type-5 routes
             (bgp_routemap.c).";
          leaf ipv4 {
            type inet:ipv4-address-no-zone;
          }
          leaf ipv6 {
            type inet:ipv6-address-no-zone;
          }
        }
        leaf evpn-rmac {
          type yang:mac-address;
          description
            "'set extcommunity evpn rmac X:X:X:X:X:X': Router MAC
             extended community (bgp_routemap.c).";
        }
      }
    }
  }
}
